# SystemRequirements

## #1: Sensors (Container)

### #2: Proximity Sensors (Functional)
The Self Navigating Robot shall have three digital switch sensors.

## #5: Actuation (Container)

### #4: Actuation (Functional)
The Self Navigating Robot shall use two motors for steering and drive control.

### #13: Indication of turning (Functional)
The self-navigating robot shall use LEDs to represent idicators when turning.

### #14: Indication of braking (Functional)
The self-navigating robot shall use LEDs to represent brake lights when stopping.

### #15: Indication of reversing (Functional)
The self-navigating robot shall have LEDs used to indicate when reversing.

## #6: Control (Container)

### #12: Manage motors (Functional)
The Controller shall manage the demands to the motors depending on the sensor measurements.

### #16: Wireless Control (Functional)
The self-navigating robot shall have a wireless transmitter

### #17: On-Off (Functional)
The self-navigating robot shall have an on-off switch.

### #18: H-Bridge Motor Control (Functional)
The self-navigating robot shall use a H-Bridge for switching the motors.

## #19: Justifications

### #20: On-Off Switch Justification
The On-Off Switch functionality will be achieved by hardware outside the software model.

### #21: H-Bridge Motor Control Justification
The electrical control and protection circuit will be achieved through electronics outside of the software model.
