# ControllerRequirements

## #1: Controller Behaviour (Container)

### #3: Left-Collision (Functional)
If the Left Proximity Sensor is triggered, then the Self Navigating Robot shall stop. Reverse. Then turn right 90 degrees before continuing to drive forward.

### #4: Right-Collision (Functional)
If the Right Proximity Sensor is triggered, then the Self Navigating Robot shall stop. Reverse. Then turn left 90 degrees before continuing to drive forward.

### #5: Front-Collision (Functional)
If the Front Proximity Sensor is triggered, then the Self Navigating Robot shall stop. Reverse. Then turn right 90 degrees before continuing to drive forward.

### #7: Default Driving (Functional)
The normal drive control mode shall be for the Self Navigating Robot to drive forwards.
